MetadataModule DEFINITIONS AUTOMATIC TAGS ::= BEGIN

  EXPORTS Metadata;

  -- https://sourceforge.net/p/asn1c/discussion/357921/thread/aced2512/
  IMPORTS Length,
          Positive,
          RoleType,
          Signatures,
          UTCDateTime       FROM CommonModule
          RootMetadata      FROM RootModule
          TargetsMetadata   FROM TargetsModule
          SnapshotMetadata  FROM SnapshotModule
          TimestampMetadata FROM TimestampModule;

  Metadata      ::= SEQUENCE {
    signed              Signed,
    numberOfSignatures  Length,
    signatures          Signatures
  }
  Signed        ::= SEQUENCE {
    type        RoleType,
    expires     UTCDateTime,
    version     Positive,
    body        SignedBody
  }
  SignedBody    ::= CHOICE {
    rootMetadata      RootMetadata,
    targetsMetadata   TargetsMetadata,
    snapshotMetadata  SnapshotMetadata,
    timestampMetadata TimestampMetadata
  }

END
