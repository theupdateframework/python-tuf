TrustPinningModule DEFINITIONS AUTOMATIC TAGS ::= BEGIN

  IMPORTS Length,
          Paths,
          StrictFilename,
          URLs FROM CommonModule;

  -- https://github.com/theupdateframework/taps/blob/master/tap4.md
  TrustPinning ::= SEQUENCE {
    -- A list of repositories.
    numberOfRepositories  Length,
    repositories          Repositories,
    --A list of multi-repository delegations.
    numberOfDelegations   Length,
    delegations           RepositoryDelegations
  }

  -- Adjust length of SEQUENCE OF to your needs.
  Repositories    ::= SEQUENCE (SIZE(1..8)) OF Repository
  Repository      ::= SEQUENCE {
    -- A shorthand name for the repository.
    name              RepositoryName,
    -- The base URL to the repository.
    numberOfMirrors   Length,
    mirrors           URLs,
    -- The name of the directory on the client which contains previous and
    -- current metadata.
    metadataDirectory StrictFilename
  }
  -- Adjust length of SEQUENCE OF to your needs.
  RepositoryNames ::= SEQUENCE (SIZE(2)) OF RepositoryName
  RepositoryName  ::= StrictFilename

  -- Adjust length of SEQUENCE OF to your needs.
  RepositoryDelegations ::= SEQUENCE (SIZE(1)) OF RepositoryDelegation
  RepositoryDelegation  ::= SEQUENCE {
    -- The list of targets delegated to the following repositories.
    numberOfPaths Length,
    paths         Paths,
    -- The repositories which MUST all sign the preceeding targets.
    numberOfRepositories  Length,
    repositories          RepositoryNames,
    -- Whether or not this delegation is terminating.
    terminating   BOOLEAN DEFAULT FALSE
  }

END
