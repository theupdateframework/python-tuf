-- $ asn1c -EF CommonModule.asn1 MetadataModule.asn1  RootModule.asn1 TargetsModule.asn1 SnapshotModule.asn1 TimestampModule.asn1 TimeServerModule.asn1 ECUModule.asn1 > ecumodule.asn1
-- To keep asn1ate happy, had to remove:
-- 1. PATTERN constraints on VisibleString.
-- 2. Module definitions in between.

ECUModule DEFINITIONS AUTOMATIC TAGS ::=
BEGIN

RoleType ::= ENUMERATED {
    root(0),
    targets(1),
    snapshot(2),
    timestamp(3)
}

Filename ::= VisibleString (SIZE(1..32))

StrictFilename ::= VisibleString (SIZE(1..32))

BitString ::= BIT STRING (SIZE(1..1024))

OctetString ::= OCTET STRING (SIZE(1..1024))

Paths ::= SEQUENCE (SIZE(1..8)) OF Path

Path ::= VisibleString (SIZE(1..32))

URLs ::= SEQUENCE (SIZE(0..8)) OF URL

URL ::= VisibleString (SIZE(1..1024))

Identifier ::= VisibleString (SIZE(1..32))

Natural ::= INTEGER (0..MAX)

Positive ::= INTEGER (1..MAX)

Length ::= Positive

Threshold ::= Positive

Version ::= Positive

UTCDateTime ::= Positive

BinaryData ::= CHOICE {
    bitString	 [0] IMPLICIT BitString,
    octetString	 [1] IMPLICIT OctetString
}

Hashes ::= SEQUENCE (SIZE(1..8)) OF Hash

Hash ::= SEQUENCE {
    function	 [0] IMPLICIT HashFunction,
    digest	 [1] EXPLICIT BinaryData
}

HashFunction ::= ENUMERATED {
    sha224(0),
    sha256(1),
    sha384(2),
    sha512(3),
    sha512-224(4),
    sha512-256(5),
    ...
}

Keyids ::= SEQUENCE (SIZE(1..8)) OF Keyid

Keyid ::= BinaryData

Signatures ::= SEQUENCE (SIZE(1..8)) OF Signature

Signature ::= SEQUENCE {
    keyid	 [0] EXPLICIT Keyid,
    method	 [1] IMPLICIT SignatureMethod,
    hash	 [2] IMPLICIT Hash,
    value	 [3] EXPLICIT BinaryData
}

SignatureMethod ::= ENUMERATED {
    rsassa-pss(0),
    ed25519(1),
    ...
}

PublicKeys ::= SEQUENCE (SIZE(1..8)) OF PublicKey

PublicKey ::= SEQUENCE {
    publicKeyid	 [0] EXPLICIT Keyid,
    publicKeyType	 [1] IMPLICIT PublicKeyType,
    publicKeyValue	 [2] EXPLICIT BinaryData
}

PublicKeyType ::= ENUMERATED {
    rsa(0),
    ed25519(1),
    ...
}

Metadata ::= SEQUENCE {
    signed	 [0] IMPLICIT Signed,
    numberOfSignatures	 [1] IMPLICIT Length,
    signatures	 [2] IMPLICIT Signatures
}

Signed ::= SEQUENCE {
    type	 [0] IMPLICIT RoleType,
    expires	 [1] IMPLICIT UTCDateTime,
    version	 [2] IMPLICIT Positive,
    body	 [3] EXPLICIT SignedBody
}

SignedBody ::= CHOICE {
    rootMetadata	 [0] IMPLICIT RootMetadata,
    targetsMetadata	 [1] IMPLICIT TargetsMetadata,
    snapshotMetadata	 [2] IMPLICIT SnapshotMetadata,
    timestampMetadata	 [3] IMPLICIT TimestampMetadata
}

RootMetadata ::= SEQUENCE {
    numberOfKeys	 [0] IMPLICIT Length,
    keys	 [1] IMPLICIT PublicKeys,
    numberOfRoles	 [2] IMPLICIT Length,
    roles	 [3] IMPLICIT TopLevelRoles,
    ...
}

TopLevelRoles ::= SEQUENCE (SIZE(4)) OF TopLevelRole

TopLevelRole ::= SEQUENCE {
    role	 [0] IMPLICIT RoleType,
    numberOfURLs	 [1] IMPLICIT Length OPTIONAL,
    urls	 [2] IMPLICIT URLs OPTIONAL,
    numberOfKeyids	 [3] IMPLICIT Length,
    keyids	 [4] IMPLICIT Keyids,
    threshold	 [5] IMPLICIT Threshold,
    ...
}

TargetsMetadata ::= SEQUENCE {
    numberOfTargets	 [0] IMPLICIT Natural,
    targets	 [1] IMPLICIT Targets,
    delegations	 [2] IMPLICIT TargetsDelegations OPTIONAL,
    ...
}

Targets ::= SEQUENCE (SIZE(1..128)) OF TargetAndCustom

TargetAndCustom ::= SEQUENCE {
    target	 [0] IMPLICIT Target,
    custom	 [1] IMPLICIT Custom OPTIONAL
}

Target ::= SEQUENCE {
    filename	 [0] IMPLICIT Filename,
    length	 [1] IMPLICIT Length,
    numberOfHashes	 [2] IMPLICIT Length,
    hashes	 [3] IMPLICIT Hashes
}

Custom ::= SEQUENCE {
    releaseCounter	 [0] IMPLICIT Natural OPTIONAL,
    hardwareIdentifier	 [1] IMPLICIT Identifier OPTIONAL,
    ecuIdentifier	 [2] IMPLICIT Identifier OPTIONAL,
    encryptedTarget	 [3] IMPLICIT Target OPTIONAL,
    encryptedSymmetricKey	 [4] IMPLICIT EncryptedSymmetricKey OPTIONAL,
    ...
}

EncryptedSymmetricKey ::= SEQUENCE {
    encryptedSymmetricKeyType	 [0] IMPLICIT EncryptedSymmetricKeyType,
    encryptedSymmetricKeyValue	 [1] EXPLICIT BinaryData
}

EncryptedSymmetricKeyType ::= ENUMERATED {
    aes128(0),
    aes192(1),
    aes256(2),
    ...
}

TargetsDelegations ::= SEQUENCE {
    numberOfKeys	 [0] IMPLICIT Length,
    keys	 [1] IMPLICIT PublicKeys,
    numberOfDelegations	 [2] IMPLICIT Length,
    delegations	 [3] IMPLICIT PrioritizedPathsToRoles
}

PrioritizedPathsToRoles ::= SEQUENCE (SIZE(1..8)) OF PathsToRoles

PathsToRoles ::= SEQUENCE {
    numberOfPaths	 [0] IMPLICIT Length,
    paths	 [1] IMPLICIT Paths,
    numberOfRoles	 [2] IMPLICIT Length,
    roles	 [3] IMPLICIT MultiRoles,
    terminating	 [4] IMPLICIT BOOLEAN DEFAULT FALSE
}

MultiRoles ::= SEQUENCE (SIZE(1..8)) OF MultiRole

MultiRole ::= SEQUENCE {
    rolename	 [0] IMPLICIT StrictFilename,
    numberOfKeyids	 [1] IMPLICIT Length,
    keyids	 [2] IMPLICIT Keyids,
    threshold	 [3] IMPLICIT Threshold
}

SnapshotMetadata ::= SEQUENCE {
    numberOfSnapshotMetadataFiles	 [0] IMPLICIT Length,
    snapshotMetadataFiles	 [1] IMPLICIT SnapshotMetadataFiles
}

SnapshotMetadataFiles ::= SEQUENCE (SIZE(1..128)) OF SnapshotMetadataFile

SnapshotMetadataFile ::= SEQUENCE {
    filename	 [0] IMPLICIT StrictFilename,
    version	 [1] IMPLICIT Version,
    ...
}

TimestampMetadata ::= SEQUENCE {
    filename	 [0] IMPLICIT Filename,
    version	 [1] IMPLICIT Version,
    length	 [2] IMPLICIT Length,
    numberOfHashes	 [3] IMPLICIT Length,
    hashes	 [4] IMPLICIT Hashes,
    ...
}

SequenceOfTokens ::= SEQUENCE {
    numberOfTokens	 [0] IMPLICIT Length,
    tokens	 [1] IMPLICIT Tokens
}

Tokens ::= SEQUENCE (SIZE(1..128)) OF Token

Token ::= INTEGER

CurrentTime ::= SEQUENCE {
    signed	 [0] IMPLICIT TokensAndTimestamp,
    numberOfSignatures	 [1] IMPLICIT Length,
    signatures	 [2] IMPLICIT Signatures
}

TokensAndTimestamp ::= SEQUENCE {
    numberOfTokens	 [0] IMPLICIT Length,
    tokens	 [1] IMPLICIT Tokens,
    timestamp	 [2] IMPLICIT UTCDateTime,
    ...
}

VehicleVersionManifest ::= SEQUENCE {
    signed	 [0] IMPLICIT VehicleVersionManifestSigned,
    numberOfSignatures	 [1] IMPLICIT Length,
    signatures	 [2] IMPLICIT Signatures
}

VehicleVersionManifestSigned ::= SEQUENCE {
    vehicleIdentifier	 [0] IMPLICIT Identifier,
    primaryIdentifier	 [1] IMPLICIT Identifier,
    numberOfECUVersionManifests	 [2] IMPLICIT Length,
    ecuVersionManifests	 [3] IMPLICIT ECUVersionManifests,
    securityAttack	 [4] IMPLICIT VisibleString (SIZE(1..1024)) OPTIONAL,
    ...
}

ECUVersionManifests ::= SEQUENCE (SIZE(1..128)) OF ECUVersionManifest

VersionReport ::= SEQUENCE {
    tokenForTimeServer	 [0] IMPLICIT Token,
    ecuVersionManifest	 [1] IMPLICIT ECUVersionManifest,
    ...
}

ECUVersionManifest ::= SEQUENCE {
    signed	 [0] IMPLICIT ECUVersionManifestSigned,
    numberOfSignatures	 [1] IMPLICIT Length,
    signatures	 [2] IMPLICIT Signatures
}

ECUVersionManifestSigned ::= SEQUENCE {
    ecuIdentifier	 [0] IMPLICIT Identifier,
    previousTime	 [1] IMPLICIT UTCDateTime,
    currentTime	 [2] IMPLICIT UTCDateTime,
    securityAttack	 [3] IMPLICIT VisibleString (SIZE(1..1024)) OPTIONAL,
    installedImage	 [4] IMPLICIT Target,
    ...
}

MetadataFiles ::= SEQUENCE {
    setGUID	 [0] IMPLICIT INTEGER,
    numberOfMetadataFiles	 [1] IMPLICIT Length
}

MetadataFile ::= SEQUENCE {
    setGUID	 [0] IMPLICIT INTEGER,
    fileNumber	 [1] IMPLICIT Positive,
    filename	 [2] IMPLICIT Filename,
    metadata	 [3] IMPLICIT Metadata
}

ImageRequest ::= SEQUENCE {
    filename	 [0] IMPLICIT Filename,
    ...
}

ImageFile ::= SEQUENCE {
    filename	 [0] IMPLICIT Filename,
    numberOfBlocks	 [1] IMPLICIT Positive,
    blockSize	 [2] IMPLICIT Positive
}

ImageBlock ::= SEQUENCE {
    filename	 [0] IMPLICIT Filename,
    blockNumber	 [1] IMPLICIT Positive,
    block	 [2] EXPLICIT BinaryData
}

END
