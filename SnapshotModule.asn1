SnapshotModule DEFINITIONS AUTOMATIC TAGS ::= BEGIN

  EXPORTS SnapshotMetadata;

  IMPORTS Length,
          Hashes,
          StrictFilename,
          Version FROM CommonModule;

  -- Adjust length of SEQUENCE OF to your needs.
  SnapshotMetadata ::= SEQUENCE {
    numberOfSnapshotMetadataFiles Length,
    snapshotMetadataFiles         SnapshotMetadataFiles
  }
  SnapshotMetadataFiles ::= SEQUENCE (SIZE(1..128)) OF SnapshotMetadataFile
  SnapshotMetadataFile ::= SEQUENCE {
    filename  StrictFilename,
    version   Version,
    -- https://tools.ietf.org/html/rfc6025#section-2.4.2
    ...
  }

END
