TimestampModule DEFINITIONS AUTOMATIC TAGS ::= BEGIN

  EXPORTS TimestampMetadata;

  IMPORTS Filename,
          Hashes,
          Length,
          Version FROM CommonModule;

  TimestampMetadata ::= SEQUENCE {
    filename        Filename,
    version         Version,
    length          Length,
    numberOfHashes  Length,
    hashes          Hashes,
    -- https://tools.ietf.org/html/rfc6025#section-2.4.2
    ...
  }


END
