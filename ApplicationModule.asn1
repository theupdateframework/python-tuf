ApplicationModule DEFINITIONS AUTOMATIC TAGS ::= BEGIN

  IMPORTS BinaryData,
          Filename,
          Identifier,
          Length,
          Positive,
          Signatures          FROM CommonModule
          Metadata            FROM MetadataModule
          ECUVersionManifest  FROM BootloaderModule;

  -- What a primary sends the director repository.
  VehicleVersionManifest ::= SEQUENCE {
    -- The signed portion of the manifest.
    signed    VehicleVersionManifestSigned,
    -- The signature on the hash of the signed portion.
    numberOfSignatures  Length,
    signatures          Signatures
  }
  VehicleVersionManifestSigned ::= SEQUENCE {
    -- A unique identifier for the vehicle.
    vehicleIdentifier           Identifier,
    -- A unique identifier for the primary sending this manifest.
    primaryIdentifier           Identifier,
    numberOfECUVersionManifests Length,
    -- An ECU version manifest per secondary.
    ecuVersionManifests         ECUVersionManifests,
    -- https://tools.ietf.org/html/rfc6025#section-2.4.2
    ...
  }
  -- Adjust length of SEQUENCE OF to your needs.
  ECUVersionManifests ::= SEQUENCE (SIZE(1..128)) OF ECUVersionManifest

  -- A signal from a primary to its secondaries that new metadata will be
  -- broadcast.
  MetadataBroadcast ::= SEQUENCE {
    -- A globally unique identifier (e.g., a monotonically increasing counter)
    -- for this broadcast session.
    broadcastGUID INTEGER,
    -- The number of metadata files that will be broadcast in this session.
    numberOfMetadataFiles Length
  }
  MetadataFile ::= SEQUENCE {
    -- The broadcast session associated with this metadata file.
    broadcastGUID INTEGER,
    -- The file number in this broadcast.
    fileNumber    Positive,
    -- The metadata filename.
    filename      Filename,
    -- The metadata itself.
    metadata      Metadata
  }

  ImageFile ::= SEQUENCE {
    -- An image filename.
    filename        Filename,
    -- The number of blocks in this image file.
    numberOfBlocks  Positive,
    -- The size of each block.
    blockSize       Positive
  }
  ImageBlock ::= SEQUENCE {
    -- The filename of the image associated with this block.
    filename    Filename,
    -- The block number of the image file.
    blockNumber Positive,
    -- The image block itself.
    block       BinaryData
  }

END
