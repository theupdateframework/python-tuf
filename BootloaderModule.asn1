BootloaderModule DEFINITIONS AUTOMATIC TAGS ::= BEGIN

  EXPORTS ECUVersionManifest;

  IMPORTS Filename,
          Identifier,
          Length,
          Signatures,
          UTCDateTime FROM CommonModule
          Target      FROM TargetsModule
          Nonce       FROM TimeServerModule;

  -- What a secondary without additional storage sends its primary to request an
  -- image.
  ImageRequest ::= SEQUENCE {
    filename Filename,
    -- https://tools.ietf.org/html/rfc6025#section-2.4.2
    ...
  }

  -- What a secondary sends its primary after reboot.
  VersionReport ::= SEQUENCE {
    -- Nonce for the time server.
    nonceForTimeServer Nonce,
    -- The ECU version manifest for the director.
    ecuVersionManifest ECUVersionManifest,
    ...
  }
  ECUVersionManifest ::= SEQUENCE {
    -- The signed portion of the manifest.
    signed      ECUVersionManifestSigned,
    -- The signature on the hash of the signed portion.
    numberOfSignatures  Length,
    signatures          Signatures
  }
  ECUVersionManifestSigned ::= SEQUENCE {
    -- A unique identifier for the ECU.
    ecuIdentifier   Identifier,
    -- The previous time seen on the time server.
    previousTime    UTCDateTime,
    -- The latest known time seen on the time server.
    currentTime     UTCDateTime,
    -- A message about a detected security attack, if any.
    securityAttack  VisibleString (SIZE(1..1024)) OPTIONAL,
    -- Metadata about the installed image.
    installedImage  Target,
    ...
  }

END
